FME workspace validate_AirBnB.fmw

Inspector
Inspector_2

Bookmark: Read CSV
Creator
    GEOMTYPE = Geometry Object
    NUM = 1
    CREATED -> FeatureReader [INITIATOR]
FeatureReader
    ATTRIBUTES = CSV,"id,listing_url,scrape_id,last_scraped,name,summary,space,description,experiences_offered,neighborhood_overview,notes,transit,access,interaction,house_rules,thumbnail_url,medium_url,picture_url,xl_picture_url,host_id,host_url,host_name,host_since,host_location,host_about,host_response_time,host_response_rate,host_acceptance_rate,host_is_superhost,host_thumbnail_url,host_picture_url,host_neighbourhood,host_listings_count,host_total_listings_count,host_verifications,host_has_profile_pic,host_identity_verified,street,neighbourhood,neighbourhood_cleansed,neighbourhood_group_cleansed,city,state,zipcode,market,smart_location,country_code,country,latitude,longitude,is_location_exact,property_type,room_type,accommodates,bathrooms,bedrooms,beds,bed_type,amenities,square_feet,price,weekly_price,monthly_price,security_deposit,cleaning_fee,guests_included,extra_people,minimum_nights,maximum_nights,minimum_minimum_nights,maximum_minimum_nights,minimum_maximum_nights,maximum_maximum_nights,minimum_nights_avg_ntm,maximum_nights_avg_ntm,calendar_updated,has_availability,availability_30,availability_60,availability_90,availability_365,calendar_last_scraped,number_of_reviews,number_of_reviews_ltm,first_review,last_review,review_scores_rating,review_scores_accuracy,review_scores_cleanliness,review_scores_checkin,review_scores_communication,review_scores_location,review_scores_value,requires_license,license,jurisdiction_names,instant_bookable,is_business_travel_ready,cancellation_policy,require_guest_profile_picture,require_guest_phone_verification,calculated_host_listings_count,calculated_host_listings_count_entire_homes,calculated_host_listings_count_private_rooms,calculated_host_listings_count_shared_rooms,reviews_per_month"
    ATTR_ACCUM_MODE = Only Use Result
    COMBINE_GEOM = Use Result
    CSV2_CASE_SENSITIVE_FIELD_NAMES = Yes
    CSV2_DATA_START_LINE = 2
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 10000
    CSV2_SCAN_TYPES = Yes
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\Users\IvodeLiefdeTensing\OneDrive - Tensing\Documents\Projects\fme_sklearn\Data\AirBnB_amsterdam.csv
    FEATURETYPES = CSV
    FORMAT = CSV2
    INTERACT = <No Spatial Filter>
    OUTPUT_FEATURES_DISPLAY = Schema and Data Features
    CSV -> Counter

Bookmark: Test split
Counter
    CNT_ATTR = _count
    DOMAIN = counter
    SCOPE = Global
    START = 0
    -> TestFilter
TestFilter
    DEFAULT_VALUE = validate
    TEST_LIST = "BOOL_OP,OR,COMPOSITE_TEST,""""""1"""""",TEST_CLAUSE,TEST @Value(_count) < 15000",train
    validate -> AttributeKeeper
    validate -> StringReplacer_4

Bookmark: Prepare attributes
AttributeKeeper
    KEEP_ATTRS = accommodates,availability_30,availability_60,availability_90,availability_365,bathrooms,bedrooms,beds,host_acceptance_rate,host_listings_count,host_response_rate,host_total_listings_count,maximum_maximum_nights,maximum_minimum_nights,maximum_nights,maximum_nights_avg_ntm,minimum_maximum_nights,minimum_minimum_nights,minimum_nights,minimum_nights_avg_ntm,number_of_reviews,number_of_reviews_ltm,require_guest_phone_verification,require_guest_profile_picture,requires_license,review_scores_accuracy,review_scores_checkin,review_scores_cleanliness,review_scores_communication,review_scores_location,review_scores_rating,review_scores_value,reviews_per_month,security_deposit,has_availability,host_has_profile_pic,host_is_superhost,is_business_travel_ready,is_location_exact
    -> StringReplacer
StringReplacer
    CASE = NO
    FIND_TEXT = f
    NO_MATCH = 1
    REGEXP = NO
    REPLACE_TEXT = 0
    SRC_ATTRS = has_availability,host_has_profile_pic,host_is_superhost,host_listings_count,host_total_listings_count,is_business_travel_ready,is_location_exact,require_guest_phone_verification,require_guest_profile_picture,requires_license
    -> AttributeTrimmer
AttributeTrimmer
    SRC_ATTRS = accommodates,availability_30,availability_60,availability_90,availability_365,bathrooms,bedrooms,beds,has_availability,host_acceptance_rate,host_has_profile_pic,host_is_superhost,host_listings_count,host_response_rate,host_total_listings_count,is_business_travel_ready,is_location_exact,maximum_maximum_nights,maximum_minimum_nights,maximum_nights,maximum_nights_avg_ntm,minimum_maximum_nights,minimum_minimum_nights,minimum_nights,minimum_nights_avg_ntm,number_of_reviews,number_of_reviews_ltm,require_guest_phone_verification,require_guest_profile_picture,requires_license,review_scores_accuracy,review_scores_checkin,review_scores_cleanliness,review_scores_communication,review_scores_location,review_scores_rating,review_scores_value,reviews_per_month,security_deposit
    TRIM_CHARS = $%
    TRIM_TO_NONE = Yes
    TRIM_TYPE = Both
    -> StringReplacer_2
StringReplacer_2
    CASE = NO
    FIND_TEXT = N/A
    NO_MATCH = _FME_NO_OP_
    REGEXP = NO
    SRC_ATTRS = accommodates,availability_30,availability_60,availability_90,availability_365,bathrooms,bedrooms,beds,has_availability,host_acceptance_rate,host_has_profile_pic,host_is_superhost,host_listings_count,host_response_rate,host_total_listings_count,is_business_travel_ready,is_location_exact,maximum_maximum_nights,maximum_minimum_nights,maximum_nights,maximum_nights_avg_ntm,minimum_maximum_nights,minimum_minimum_nights,minimum_nights,minimum_nights_avg_ntm,number_of_reviews,number_of_reviews_ltm,require_guest_phone_verification,require_guest_profile_picture,requires_license,review_scores_accuracy,review_scores_checkin,review_scores_cleanliness,review_scores_communication,review_scores_location,review_scores_rating,review_scores_value,reviews_per_month,security_deposit
    -> StringReplacer_3
StringReplacer_3
    CASE = NO
    FIND_TEXT = ,
    NO_MATCH = _FME_NO_OP_
    REGEXP = NO
    SRC_ATTRS = accommodates,availability_30,availability_60,availability_90,availability_365,bathrooms,bedrooms,beds,has_availability,host_acceptance_rate,host_has_profile_pic,host_is_superhost,host_listings_count,host_response_rate,host_total_listings_count,is_business_travel_ready,is_location_exact,maximum_maximum_nights,maximum_minimum_nights,maximum_nights,maximum_nights_avg_ntm,minimum_maximum_nights,minimum_minimum_nights,minimum_nights,minimum_nights_avg_ntm,number_of_reviews,number_of_reviews_ltm,require_guest_phone_verification,require_guest_profile_picture,requires_license,review_scores_accuracy,review_scores_checkin,review_scores_cleanliness,review_scores_communication,review_scores_location,review_scores_rating,review_scores_value,reviews_per_month,security_deposit
    -> AttributeManager
AttributeManager
    ATTR_TABLE = SET_TO security_deposit = @ReplaceRegEx(@Value(security_deposit),",","")
    -> StringFormatter
StringFormatter
    FORMAT = f
    SRC_ATTRS = accommodates,availability_30,availability_60,availability_90,availability_365,bathrooms,bedrooms,beds,has_availability,host_acceptance_rate,host_has_profile_pic,host_is_superhost,host_listings_count,host_response_rate,host_total_listings_count,is_business_travel_ready,is_location_exact,maximum_maximum_nights,maximum_minimum_nights,maximum_nights,maximum_nights_avg_ntm,minimum_maximum_nights,minimum_minimum_nights,minimum_nights,minimum_nights_avg_ntm,number_of_reviews,number_of_reviews_ltm,require_guest_phone_verification,require_guest_profile_picture,requires_license,review_scores_accuracy,review_scores_checkin,review_scores_cleanliness,review_scores_communication,review_scores_location,review_scores_rating,review_scores_value,reviews_per_month,security_deposit
    -> NullAttributeMapper
NullAttributeMapper
    ATTRCHOICE = Selected Attributes
    ATTRLIST = host_acceptance_rate host_response_rate security_deposit
    NEW_VALUE = 0
    NULL_TREATMENT = New Value
    SOURCE_ATTR_VAL = Null Empty "Missing (Selected Attributes Only)"
    -> sklearn_predict

Bookmark: Predict price using trained model
sklearn_predict
    input_path = C:\Users\IvodeLiefdeTensing\OneDrive - Tensing\Documents\Projects\fme_sklearn\airbnb.joblib
    -> Counter_2

Bookmark: Compare price and prediction
Counter_2
    CNT_ATTR = _count
    DOMAIN = counter
    SCOPE = Local
    START = 0
    -> FeatureMerger [REQUESTOR]
StringReplacer_4
    CASE = NO
    FIND_TEXT = ,
    NO_MATCH = _FME_NO_OP_
    REGEXP = NO
    SRC_ATTRS = price
    -> AttributeTrimmer_2
AttributeTrimmer_2
    SRC_ATTRS = price
    TRIM_CHARS = $%
    TRIM_TO_NONE = Yes
    TRIM_TYPE = Both
    -> Counter_3
Counter_3
    CNT_ATTR = _count
    DOMAIN = counter
    SCOPE = Local
    START = 0
    -> FeatureMerger [SUPPLIER]
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> AttributeExposer
AttributeExposer
    ATTR_LIST = prediction
    -> AttributeKeeper_2
AttributeKeeper_2
    KEEP_ATTRS = price,prediction,_count
    -> AttributeCreator
AttributeCreator
    ATTR_TABLE:
      SET_TO error = @Evaluate(@Value(price) - @Value(prediction))
      SET_TO abs_error = @Evaluate(@abs(@Value(error)))
    -> TestFilter_2
TestFilter_2
    DEFAULT_VALUE = No prediction possible
    TEST_LIST = "BOOL_OP,OR,COMPOSITE_TEST,""""""1"""""",TEST_CLAUSE,CASE_SENSITIVE_TEST @Value(prediction) CONTAINS_REGEX .+",Prediction
    Prediction -> StatisticsCalculator
    Prediction -> Inspector_2
StatisticsCalculator
    CALCULATION_MODE = NUMERIC
    FEAT_STATS = abs_error,MIN,MAX,,,MEAN,MEDIAN,,RANGE,,STDEV_P,,HIST;error,MIN,MAX,,,MEAN,MEDIAN,,RANGE,,STDEV_P,,HIST;prediction,MIN,MAX,COUNT,,MEAN,MEDIAN,,RANGE,,STDEV_P,,HIST;price,MIN,MAX,COUNT,,MEAN,MEDIAN,,RANGE,,STDEV_P,,HIST
    SUMMARY -> Inspector
